module org-openroadm-common-network {
  yang-version 1.1;
  namespace "http://org/openroadm/common/network";
  prefix cnet;

  import ietf-network {
    prefix nd;
    revision-date 2018-02-26;
  }
  import ietf-network-topology {
    prefix nwt;
    revision-date 2018-02-26;
  }
  import org-openroadm-network-types {
    prefix org-openroadm-network-types;
  }
  import org-openroadm-common-state-types {
    prefix org-openroadm-common-state-types;
  }
  import org-openroadm-equipment-states-types {
    prefix org-openroadm-equipment-states-types;
  }

  organization
    "OPEN ROADM MSA";
  contact
    "www.OpenROADM.org.";
  description
    "Copyright of the Members of the Open ROADM MSA Agreement dated (c) 2016,
     All other rights reserved.

     Redistribution and use in source and binary forms, with or without modification,
     are permitted provided that the following conditions are met:

     * Redistributions of source code must retain the above copyright notice, this
       list of conditions and the following disclaimer.
     * Redistributions in binary form must reproduce the above copyright notice,
       this list of conditions and the following disclaimer in the documentation and/or
       other materials provided with the distribution.
     * Neither the Members of the Open ROADM MSA Agreement nor the names of its
       contributors may be used to endorse or promote products derived from this software
       without specific prior written permission.

     THIS SOFTWARE IS PROVIDED BY THE MEMBERS OF THE OPEN ROADM MSA  AGREEMENT ''AS IS''
     AND ANY EXPRESS OR IMPLIED WARRANTIES, INCLUDING, BUT NOT LIMITED TO, THE IMPLIED
     WARRANTIES OF MERCHANTABILITY AND FITNESS FOR A PARTICULAR PURPOSE ARE DISCLAIMED.
     IN NO EVENT THE MEMBERS OF THE OPEN ROADM MSA  AGREEMENT BE LIABLE FOR ANY DIRECT,
     INDIRECT, INCIDENTAL, SPECIAL, EXEMPLARY, OR CONSEQUENTIAL DAMAGES (INCLUDING, BUT
     NOT LIMITED TO, PROCUREMENT OF SUBSTITUTE GOODS OR SERVICES;  LOSS OF USE, DATA,
     OR PROFITS; OR BUSINESS INTERRUPTION) HOWEVER CAUSED AND ON ANY THEORY OF LIABILITY,
     WHETHER IN CONTRACT, STRICT LIABILITY, OR TORT (INCLUDING NEGLIGENCE OR OTHERWISE)
     ARISING IN ANY WAY OUT OF THE USE OF THIS SOFTWARE, EVEN IF ADVISED OF THE
     POSSIBILITY OF SUCH DAMAGE.";

  revision 2022-05-27 {
    description
      "Version 11.1";
  }

  augment "/nd:networks/nd:network/nd:network-types" {
    description
      "Introduce new network type for the Open ROADM common network";
    container openroadm-common-network {
      presence "indicates common network of Open ROADMs";
      description
        "The presence of the container node indicates Open ROADM common network";
    }
  }

  augment "/nd:networks/nd:network/nd:node" {
    description
      "Augment the generic network node with Open ROADM common attributes.";
    leaf node-type {
      type org-openroadm-network-types:openroadm-node-type;
      description
        "A component of the network topology. Once the node-type is configured, it should not be modified.";
    }
    leaf lifecycle-state {
      type org-openroadm-common-state-types:lifecycle-state;
      description
        "Lifecycle State of a node. Whether it is planned, deployed, in maintenance, etc.";
    }
    leaf operational-state {
      config false;
      type org-openroadm-common-state-types:state;
    }
    leaf administrative-state {
      type org-openroadm-equipment-states-types:admin-states;
    }
  }

  augment "/nd:networks/nd:network/nwt:link" {
    description
      "This augmentation defines common link attributes in the Open ROADM common network";
    leaf link-type {
      type org-openroadm-network-types:openroadm-link-type;
    }
    leaf opposite-link {
      type leafref {
        path "../../nwt:link/nwt:link-id";
      }
      description
        "optional - pointer to reverse link in case of bidirectional link. Supersedes opposite-link
         originally defined in OMS-attributes container, to apply to any kind of link in the topology";
    }
    leaf link-length {
      type decimal64 {
        fraction-digits 2;
      }
      units "km";
    }
    leaf link-latency {
      type uint32;
      units "microseconds";
      description
        "Latency of a link (microseconds)";
    }
    leaf administrative-group {
      type uint32;
      description
        "according to RFC 3630 definition";
    }
    leaf operational-state {
      config false;
      type org-openroadm-common-state-types:state;
    }
    leaf administrative-state {
      type org-openroadm-equipment-states-types:admin-states;
    }
    leaf lifecycle-state {
      type org-openroadm-common-state-types:lifecycle-state;
      description
        "Lifecycle State of a link. Whether it is planned, deployed, in maintenance, etc.";
    }
  }
}
