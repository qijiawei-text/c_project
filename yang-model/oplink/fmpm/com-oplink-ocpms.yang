module com-oplink-ocpms {
  namespace "http://com/oplink/ocpms";
  prefix com-oplink-ocpms;

  import openconfig-transport-pms {
    prefix openconfig-transport-pms;
  }

  organization "Oplink Communication";
  contact
    "oplink.com";
  description
    "Oplink internal YANG definitions of performance management.";
       
  revision 2017-03-14 {
    description
      "Version 1.0";
  }

    container pm-data {
      config true;

      uses openconfig-transport-pms:current-bin-15min;
      uses openconfig-transport-pms:current-bin-24h;
      uses openconfig-transport-pms:history-bins-15min;
      uses openconfig-transport-pms:history-bins-24h;
    }

}
