module ieee802-dot1dc-sched-if {
  yang-version "1.1";
  namespace urn:ieee:std:802.1Q:yang:ieee802-dot1dc-sched-if;
  prefix sched-if;
  
  import ietf-interfaces {
    prefix if;
  }
  import ieee802-dot1q-sched {
    prefix q-sched;
  }

  organization
    "Institute of Electrical and Electronics Engineers";
  contact
    "WG-URL: http://ieee802.org/1/
     WG-EMail: stds-802-1-l@ieee.org
       Contact: IEEE 802.1 Working Group Chair
       Postal: C/O IEEE 802.1 Working Group
       IEEE Standards Association
            445 Hoes Lane
            Piscataway
            NJ 08854
            USA

    E-mail: stds-802-1-chairs@ieee.org";

  description
    "This module provides for management of General Frame Quality of
    Service (GFQoS) systems that support Scheduled Traffic Enhancements.
  
    Copyright (C) IEEE (2023).

    This version of this YANG module is part of IEEE Std 802.1DC;
    see the standard itself for full legal notices.";

  revision 2023-05-16 {
    description
      "Published as part of IEEE Std 802.1DC.

      The following reference statement identifies each referenced
      IEEE Standard as updated by applicable amendments.";

    reference
      "IEEE Std 802.1DC:
      IEEE Std 802.1DC - Quality of Service Provision by
      Network Systems.";
  }

  augment "/if:interfaces/if:interface" {
    
    description
      "Augment interface with Scheduled Traffic configuration.";
    
   uses q-sched:sched-parameters;
  }
}
