module etsi-nfv-pnfd {
  yang-version 1.1;
  namespace "urn:etsi:nfv:yang:etsi-nfv-pnfd";
  prefix pnfd;

  import etsi-nfv-descriptors {
    prefix vnf;
  }

  organization
    "European Telecommunications Standards Institute (ETSI)";

  description
    "Physcial Network Function Descriptor.";

  revision 2022-03-08 {
    description
      "Version 3.6.1.

       PNFD according to ETSI GS NFV-IFA 014 Release 3.";
  }
  revision 2021-07-05 {
    description
      "Version 3.5.1.

       PNFD according to ETSI GS NFV-IFA 014 Release 3.";
  }

  revision 2020-06-10 {
    description
      "Version 3.3.1.

       PNFD according to ETSI GS NFV-IFA 014 Release 3.";
  }

  revision 2020-06-01 {
    description
      "Version 2.8.1.

       PNFD according to ETSI GS NFV-IFA 014 271.";
  }

  revision 2019-10-01 {
    description
      "Version 2.7.1.

       PNFD according to ETSI GS NFV-IFA 014 Ed271v264.";
  }

  revision 2019-04-25 {
    description
      "Initial revision.
       PNFD according to ETSI GS NFV-IFA 014 Ed261v252.";
  }

  container pnfd {
    presence "PNFD container.";
    uses vnf:pnfd;
  }
}
