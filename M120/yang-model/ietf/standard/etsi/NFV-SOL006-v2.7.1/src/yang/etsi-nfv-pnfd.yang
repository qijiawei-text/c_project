module etsi-nfv-pnfd {
  yang-version 1.1;
  namespace "urn:etsi:nfv:yang:etsi-nfv-pnfd";
  prefix pnfd;

  import etsi-nfv-descriptors {
    prefix vnf;
  }

  organization
    "European Telecommunications Standards Institute (ETSI)";

  description
    "Physcial Network Function Descriptor.";

  revision 2019-10-01 {
    description
      "Version 2.7.1.

       NSD according to ETSI GS NFV-IFA 014 Ed271v264.";
  }
  revision 2019-04-25 {
    description
      "Initial revision.
       NSD according to ETSI GS NFV-IFA 014 Ed261v252.";
  }

  container pnfd {
    presence "PNFD container.";
    uses vnf:pnfd;
  }
}
