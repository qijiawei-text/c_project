module etsi-nfv-vnfd {
  yang-version 1.1;
  namespace "urn:etsi:nfv:yang:etsi-nfv-vnfd";
  prefix vnfd;

  import etsi-nfv-descriptors {
    prefix vnf;
  }

  organization
    "European Telecommunications Standards Institute (ETSI)";

  description
    "Virtual Network Function Descriptor.";
  
  revision 2019-10-01 {
    description
      "Revision 2.7.1.
      
       VNFD according to ETSI GS NFV-IFA 011 Ed271v264.";
  }
  revision 2019-03-18 {
    description
      "Initial revision.
       VNFD according to ETSI GS NFV-IFA 011 Ed261v254.";
  }

  container vnfd {
    presence "VNFD container.";
    uses vnf:vnfd;
  }
}
