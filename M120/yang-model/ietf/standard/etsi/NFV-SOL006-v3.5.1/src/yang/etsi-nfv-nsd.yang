module etsi-nfv-nsd {
  yang-version 1.1;
  namespace "urn:etsi:nfv:yang:etsi-nfv-nsd";
  prefix nsd;

  import etsi-nfv-descriptors {
    prefix nfv;
  }

  organization
    "European Telecommunications Standards Institute (ETSI)";

  description
    "Network Services Descriptors";

  revision 2021-07-05 {
    description
      "Version 3.5.1.

       NSD according to ETSI GS NFV-IFA 014 Release 3.";
  }

  revision 2020-06-10 {
    description
      "Version 3.3.1.

       NSD according to ETSI GS NFV-IFA 014 Release 3.";
  }

  revision 2020-06-01 {
    description
      "Version 2.8.1.

       NSD according to ETSI GS NFV-IFA 014 271.";
  }

  revision 2019-10-01 {
    description
      "Version 2.7.1.

       Common data structures to support NSD according to:
       ETSI GS NFV-IFA 014 Ed271v264.";
  }

  revision 2019-04-25 {
    description
      "Initial revision.
       Common data structures to support NSD according to:
       ETSI GS NFV-IFA 014 Ed261v252.";
  }

  container nsd {
    list nsd {
      key "id";

      max-elements 1;
      uses nfv:nsd;

      description
        "The NSD information element is a deployment template whose
         instances are used by the NFVO for the lifecycle management
         of NSs.";
      reference
        "GS NFV-IFA014: Section 6.2.2, Network Service Descriptor
         information element";
    }
  }
}
